# BatterySOCReqSysInt

## batterySOC_Simulink_Temp_-10: Simulink component test RMSE for -10 Celsius (Functional)
The model must have an RMSE of less than 0.05 when compared to the test data at -10 degrees Celsius.

## batterySOC_Simulink_Temp_0: Simulink component test RMSE for 0 Celsius (Functional)
The model must have an RMSE of less than 0.05 when compared to the test data at 0 degrees Celsius.

## batterySOC_Simulink_Temp_10: Simulink component test RMSE for 10 Celsius (Functional)
The model must have an RMSE of less than 0.05 when compared to the test data at 10 degrees Celsius.

## batterySOC_Simulink_Temp_25: Simulink component test RMSE for 25 Celsius (Functional)
The model must have an RMSE of less than 0.05 when compared to the test data at 25 degrees Celsius.
