# BatterySOCReqCodeGen

## batterySOC_SIL_Temp_-10: Model MIL and SIL behavior equivalence for -10 celsius (Functional)
The model must have < 0.1% absolute tolerance when results in MIL and in SIL are compared against each other with -10 degrees celsius test data.

## batterySOC_SIL_Temp_0: Model MIL and SIL behavior equivalence for 0 celsius (Functional)
The model must have < 0.1% absolute tolerance when results in MIL and in SIL are compared against each other with 0 degrees celsius test data.

## batterySOC_SIL_Temp_10: Model MIL and SIL behavior equivalence for 10 celsius (Functional)
The model must have < 0.1% absolute tolerance when results in MIL and in SIL are compared against each other with 10 degrees celsius test data.

## batterySOC_SIL_Temp_25: Model MIL and SIL behavior equivalence for 25 celsius (Functional)
The model must have < 0.1% absolute tolerance when results in MIL and in SIL are compared against each other with 25 degrees celsius test data.
